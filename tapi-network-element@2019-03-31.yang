module tapi-network-element {
    namespace "urn:onf:otcc:yang:tapi-network-element";
    prefix tapi-network-element;
    organization
      "ONF OTCC (Open Transport Configuration & Control) Project";
    contact
      "
       Project Web: <https://wiki.opennetworking.org/display/OTCC/TAPI>
       Project List: <mailto:transport-api@opennetworking.org>
       Editor: Karthik Sethuraman
               <mailto:karthik.sethuraman@necam.com>";
    description
      "
       This module contains TAPI Network Element Model definitions.
       Source: TapiNetworkElement.uml
       Copyright (c) 2018 Open Networking Foundation (ONF). All rights reserved.
       License: This module is distributed under the Apache License 2.0";
    revision 2019-03-31 {
        description
          "ONF Transport API version 2.2-RC1.
            Changes included in this TAPI release (v2.2) are listed in
           <https://github.com/OpenNetworkingFoundation/TAPI/blob/develop/CHANGE_LOG/change-log.2.2.md>";
        reference
          "ONF-TR-527, ONF-TR-512, ONF-TR-531, RFC 7950, RFC 6087 and ONF TAPI UML model
           <https://github.com/OpenNetworkingFoundation/TAPI/tree/v2.2.0/UML>";
    }
    revision 2018-11-26 {
        description
          "ONF Transport API version 2.1.1.
           - The TAPI YANG models included in this TAPI release (v2.1.0) are a *normative* part of the TAPI SDK.
           - The YANG specifications have been generated from the corresponding UML model using the [ONF EAGLE UML2YANG mapping tool]
             <https://github.com/OpenNetworkingFoundation/EagleUmlYang>
             and further edited manually to comply with the [ONF IISOMI UML2YANG mapping guidelines]
             <https://wiki.opennetworking.org/display/OIMT/UML+-+YANG+Guidelines>
           - Status of YANG model artifacts can be determined by referring to the corresponding UML artifacts.
             As described in the UML models, some artifacts are considered *experimental*, and thus the corresponding YANG artifacts.
           - The ONF TAPI release process does not guarantee backward compatibility of YANG models across major versions of TAPI releases.
             The YANG model backward compatibility criteria are outlined in section 11 of <https://tools.ietf.org/html/rfc7950>.
             YANG models included in this release are not backward compatible with previous TAPI releases.
           - Changes included in this TAPI release (v2.1.0) are listed in
             <https://github.com/OpenNetworkingFoundation/TAPI/blob/develop/CHANGE_LOG/change-log.2.1.0.md>";
        reference
          "ONF-TR-527, ONF-TR-512, ONF-TR-531, RFC 7950, RFC 6087 and ONF TAPI UML model
           <https://github.com/OpenNetworkingFoundation/TAPI/tree/v2.1.0/UML>";
    }

    /***********************
     * package object-classes
     **********************/
    grouping connection {
        leaf ip {
            type string;
            description
              "none";
        }
        leaf port {
            type uint16;
            default 830;
            description
              "none";
        }
        leaf username {
            type string;
            description
              "none";
        }
        leaf password {
            type string;
            description
              "none";
        }
        leaf isDiscoverable {
            type boolean;
            description
              "Indication that the Network Element is Discoverable.";
        }
        description
          "none";
    }
    grouping site {
        leaf siteName {
            type string;
            description
              "none";
        }
        leaf latitude {
            type string;
            description
              "none";
        }
        leaf longitude {
            type string;
            description
              "none";
        }
        description
          "none";
    }
    grouping attributes {
        leaf role {
            type string;
            description
              "A label that can be used to define the role of the Network Element.";
        }
    }
    grouping network-element {
        leaf network-element-id {
            type string;
            description
              "The Network Element id.";
        }
        leaf network-element-name {
            type string;
            description
              "The Network Element name.";
        }
        leaf network-element-vendor {
            type string;
            description
              "The Network Element vendor.";
        }
        leaf network-element-model {
            type string;
            description
              "The Network Element model.";
        }
        leaf network-element-version {
            type string;
            description
              "The Network Element version.";
        }
        leaf network-element-lastSuccessfulDiscovery {
            type string;
            description
              "The last time the Network Element was successfully discovered.";
        }
        leaf network-element-type {
            type string;
            description
              "The Network Element type.";
        }
        uses connection;
        uses site;
        uses attributes;
        description
          "none";
    }
    /***********************
     * package interfaces
     **********************/
    rpc get-network-element-list {
        description
          "none";
        output {
            list element {
                uses network-element;
                description
                  "none";
            }
        }
    }
    rpc get-network-element-details {
        description
          "none";
        input {
            leaf network-element-id-or-name {
                type string;
                description
                  "none";
            }
        }
        output {
            container network-element {
                uses network-element;
                description
                  "none";
            }
        }
    }
    rpc create-network-element {
        description
          "none";
        input {
            container netconf-connection {
                uses connection;
                uses site;
                uses attributes;
                description
                  "none";
            }
        }
        output {
            container element {
                uses network-element;
                description
                  "none";
            }
        }
    }
    rpc delete-network-element {
        description
          "none";
        input {
            leaf network-element-id-or-name {
                type string;
                description
                  "none";
            }
        }
    }
}
